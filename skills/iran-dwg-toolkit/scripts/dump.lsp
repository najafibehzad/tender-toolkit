;; DUMP (pure vanilla LISP - no COM) - all entities to TSV
;; columns: SPACE TYPE LAYER INFO GEOM
;; works in AccCoreConsole where vlax-* COM calls are unavailable

(defun dmp:r (n) (if (numberp n) (rtos n 2 4) ""))
(defun dmp:pt (p) (if (listp p) (strcat (dmp:r (car p)) "," (dmp:r (cadr p)) (if (caddr p) (strcat "," (dmp:r (caddr p))) "")) ""))

;; join list of 2d/3d points from dxf codes
(defun dmp:pts (d code / r p) (setq r "") (foreach g d (if (= (car g) code) (setq r (strcat r (dmp:pt (cdr g)) ";")))) r)

(defun c:DUMP ( / f d e typ lyr inf geo spc closed)
  (setq f (open "C:/Users/behzad/.zcode/workspace/default/dxf-tools/entities.tsv" "w"))
  (write-line "SPACE\tTYPE\tLAYER\tINFO\tGEOM" f)
  (setq e (entnext))
  (while e
    (setq d (entget e))
    (setq typ (cdr (assoc 0 d)))
    (if (and typ (/= typ "SEQEND") (/= typ "VERTEX") (/= typ "ATTRIB"))
      (progn
        (setq lyr (cdr (assoc 8 d)))
        (setq spc (if (and (assoc 67 d) (= (cdr (assoc 67 d)) 1)) "P" "M"))
        (setq inf "")
        (setq geo "")
        (cond
          ((= typ "LINE")
            (setq geo (strcat (dmp:pt (cdr (assoc 10 d))) ";" (dmp:pt (cdr (assoc 11 d))))))
          ((= typ "LWPOLYLINE")
            (setq closed (if (and (assoc 70 d) (= 1 (logand 1 (cdr (assoc 70 d))))) "C" "O"))
            (setq geo (strcat closed ";" (dmp:pts d 10))))
          ((= typ "POLYLINE")
            (setq closed (if (and (assoc 70 d) (/= 0 (logand 1 (cdr (assoc 70 d))))) "C" "O"))
            (setq geo (strcat closed ";CLASSIC")))
          ((= typ "CIRCLE")
            (setq geo (strcat (dmp:pt (cdr (assoc 10 d))) ";" (dmp:r (cdr (assoc 40 d))))))
          ((= typ "ARC")
            (setq geo (strcat (dmp:pt (cdr (assoc 10 d))) ";" (dmp:r (cdr (assoc 40 d)))
                              ";" (dmp:r (cdr (assoc 50 d))) ";" (dmp:r (cdr (assoc 51 d))))))
          ((or (= typ "TEXT") (= typ "MTEXT"))
            (setq inf (if (assoc 1 d) (cdr (assoc 1 d)) ""))
            (setq geo (dmp:pt (cdr (assoc 10 d)))))
          ((= typ "INSERT")
            (setq inf (if (assoc 2 d) (cdr (assoc 2 d)) ""))
            (setq geo (strcat (dmp:pt (cdr (assoc 10 d)))
                              ";rot=" (dmp:r (cdr (assoc 50 d)))
                              ";sx=" (dmp:r (cdr (assoc 41 d))))))
          ((= typ "POINT")
            (setq geo (dmp:pt (cdr (assoc 10 d)))))
        )
        (write-line (strcat spc "\t" typ "\t" (if lyr lyr "") "\t" inf "\t" geo) f)
      )
    )
    (setq e (entnext e))
  )
  (close f)
  (princ "\nDUMP-DONE")
  (princ)
)
(princ "\nDUMP-LSP-LOADED")
(princ)
