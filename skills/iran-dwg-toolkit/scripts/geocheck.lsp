;; GEOCHECK - check DWG georeference vars + dump ATTRIB texts
(setq f (open "C:/Users/behzad/.zcode/workspace/default/dxf-tools/geocheck.txt" "w"))
(write-line (strcat "CGEOCS=[" (if (getvar "CGEOCS") (getvar "CGEOCS") "") "]") f)
(write-line (strcat "INSUNITS=[" (itoa (getvar "INSUNITS")) "]") f)
(write-line (strcat "AUNITS ok") f)
(close f)
(setq g (open "C:/Users/behzad/.zcode/workspace/default/dxf-tools/attribs.tsv" "w"))
(write-line "TYPE\tTAG\tTEXT" g)
(setq e (entnext))
(while e
  (setq d (entget e))
  (setq typ (cdr (assoc 0 d)))
  (if (or (= typ "ATTRIB") (= typ "ATTDEF"))
    (write-line (strcat typ "\t" (if (assoc 2 d) (cdr (assoc 2 d)) "") "\t" (if (assoc 1 d) (cdr (assoc 1 d)) "")) g)
  )
  (setq e (entnext e))
)
(close g)
(princ "\nGEOCHECK-DONE")
(princ)
